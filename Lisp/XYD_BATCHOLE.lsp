(defun XYD_BATCHOLE:read-real (regPath key default prompt allowZero / strVal val result flags)
  (setq strVal (vl-registry-read regPath key))
  (if (or (null strVal) (= strVal "")) (setq strVal default))
  (setq val (atof strVal))
  (setq flags (if allowZero 4 6))
  (initget flags)
  (setq result (getdist (strcat "\n" prompt " <" strVal ">: ")))
  (if result (setq val result))
  (vl-registry-write regPath key (rtos val 2 2))
  val
)

(defun XYD_BATCHOLE:read-int (regPath key default prompt / strVal val result)
  (setq strVal (vl-registry-read regPath key))
  (if (or (null strVal) (= strVal "")) (setq strVal default))
  (setq val (atoi strVal))
  (initget 6)
  (setq result (getint (strcat "\n" prompt " <" strVal ">: ")))
  (if result (setq val result))
  (vl-registry-write regPath key (itoa val))
  val
)

(defun XYD_BATCHOLE:restore-vars (oldVars / item)
  (foreach item oldVars
    (if (cdr item)
      (vl-catch-all-apply 'setvar (list (car item) (cdr item)))
    )
  )
)

(defun XYD_BATCHOLE:release-object (obj)
  (if (and obj (not (vlax-object-released-p obj)))
    (vl-catch-all-apply 'vlax-release-object (list obj))
  )
)

(defun XYD_BATCHOLE:collect-files (path)
  (acad_strlsort
    (append
      (vl-directory-files path "*.jpg")
      (vl-directory-files path "*.jpeg")
      (vl-directory-files path "*.png")
      (vl-directory-files path "*.bmp")
      (vl-directory-files path "*.tif")
      (vl-directory-files path "*.tiff")
    )
  )
)

(defun XYD_BATCHOLE:paste-one (doc inlineShapes wscript vbsFile fullpath x y targetHeight / shp beforeEnt ent retry obj minPt maxPt currentH currentW scaleFactor)
  (vl-catch-all-apply 'vlax-invoke (list (vlax-get-property doc 'Content) 'Delete))
  (setq shp (vl-catch-all-apply 'vlax-invoke (list inlineShapes 'AddPicture fullpath :vlax-false :vlax-true)))
  (if (vl-catch-all-error-p shp)
    nil
    (progn
      (vl-catch-all-apply 'vlax-put-property (list shp 'ScaleHeight 100))
      (vl-catch-all-apply 'vlax-put-property (list shp 'ScaleWidth 100))
      (vl-catch-all-apply 'vlax-invoke (list (vlax-get-property shp 'Range) 'Copy))
      (command "_.DELAY" 150)

      (setq retry 0)
      (setq ent nil)
      (while (and (null ent) (< retry 3))
        (setq beforeEnt (entlast))
        (vl-catch-all-apply 'vlax-invoke (list wscript 'Run (strcat "wscript.exe \"" vbsFile "\"") 0 :vlax-false))
        (vl-cmdf "_.PASTECLIP" (list x y 0.0))
        (setq ent (entlast))
        (if (eq ent beforeEnt) (setq ent nil))
        (setq retry (1+ retry))
      )

      (if (null ent)
        nil
        (progn
          (setq obj (vlax-ename->vla-object ent))
          (if (vlax-property-available-p obj 'OlePlotQuality)
            (vl-catch-all-apply 'vla-put-OlePlotQuality (list obj 2))
          )
          (if (vlax-property-available-p obj 'OutputQuality)
            (vl-catch-all-apply 'vlax-put-property (list obj 'OutputQuality 2))
          )
          (if (vlax-method-applicable-p obj 'Draw)
            (vl-catch-all-apply 'vlax-invoke (list obj 'Draw))
          )

          (setq currentH 0.0)
          (setq retry 0)
          (while (and (< currentH 1.0) (< retry 20))
            (vl-catch-all-apply 'vla-getboundingbox (list obj 'minPt 'maxPt))
            (if (and minPt maxPt)
              (progn
                (setq minPt (vlax-safearray->list minPt))
                (setq maxPt (vlax-safearray->list maxPt))
                (setq currentH (- (cadr maxPt) (cadr minPt)))
              )
            )
            (if (< currentH 1.0) (command "_.DELAY" 100))
            (setq retry (1+ retry))
          )

          (if (> currentH 1.0)
            (progn
              (setq scaleFactor (/ targetHeight currentH))
              (vl-catch-all-apply 'vla-ScaleEntity (list obj (vlax-3d-point (list x y 0.0)) scaleFactor))
              (vl-catch-all-apply 'vla-getboundingbox (list obj 'minPt 'maxPt))
              (setq minPt (vlax-safearray->list minPt))
              (setq maxPt (vlax-safearray->list maxPt))
              (setq currentW (- (car maxPt) (car minPt)))
              currentW
            )
            nil
          )
        )
      )
    )
  )
)

(defun c:XYD_BATCHOLE_LSP (/ *error* oldVars shell folder folderSelf path files regPath targetHeight gapX gapY maxCols startPt startX currentX currentY colCount rowMaxHeight wordApp docs doc inlineShapes wordOptions fso fileOut vbsFile wscript fullpath file currentW)
  (vl-load-com)
  (setq oldVars
    (list
      (cons "CMDECHO" (getvar "CMDECHO"))
      (cons "CMDDIA" (getvar "CMDDIA"))
      (cons "FILEDIA" (getvar "FILEDIA"))
      (cons "SELECTIONPREVIEW" (getvar "SELECTIONPREVIEW"))
      (cons "OLEQUALITY" (getvar "OLEQUALITY"))
      (cons "OLESTARTUP" (getvar "OLESTARTUP"))
    )
  )

  (defun *error* (msg)
    (if doc (vl-catch-all-apply 'vlax-invoke (list doc 'Close 0)))
    (if wordApp (vl-catch-all-apply 'vlax-invoke (list wordApp 'Quit)))
    (XYD_BATCHOLE:release-object inlineShapes)
    (XYD_BATCHOLE:release-object docs)
    (XYD_BATCHOLE:release-object doc)
    (XYD_BATCHOLE:release-object wordOptions)
    (XYD_BATCHOLE:release-object wordApp)
    (XYD_BATCHOLE:release-object folderSelf)
    (XYD_BATCHOLE:release-object folder)
    (XYD_BATCHOLE:release-object shell)
    (XYD_BATCHOLE:release-object wscript)
    (if (and vbsFile (findfile vbsFile)) (vl-file-delete vbsFile))
    (XYD_BATCHOLE:restore-vars oldVars)
    (if (and msg (not (wcmatch (strcase msg) "*BREAK*,*CANCEL*,*EXIT*")))
      (princ (strcat "\n[批量嵌图错误] " msg))
    )
    (princ)
  )

  (setvar "CMDECHO" 0)
  (setvar "CMDDIA" 0)
  (setvar "FILEDIA" 0)
  (setvar "OLEQUALITY" 3)
  (setvar "OLESTARTUP" 1)

  (setq regPath (strcat "HKEY_CURRENT_USER\\" (vlax-product-key) "\\Applications\\XYD_BATCHOLE_History"))
  (setq targetHeight (XYD_BATCHOLE:read-real regPath "TargetHeight" "287.0" "请输入图片目标高度" nil))
  (setq gapX (XYD_BATCHOLE:read-real regPath "GapX" "150.0" "请输入横向间距" T))
  (setq gapY (XYD_BATCHOLE:read-real regPath "GapY" "50.0" "请输入纵向间距" T))
  (setq maxCols (XYD_BATCHOLE:read-int regPath "MaxCols" "10" "请输入每行图片数量"))

  (setq startPt (getpoint "\n请在屏幕上点击指定图片的插入起始点 <默认 0,0>: "))
  (if (null startPt) (setq startPt '(0.0 0.0 0.0)))
  (setq startX (car startPt))

  (princ (strcat "\n参数确认: 高度=" (rtos targetHeight 2 2) ", 间距X=" (rtos gapX 2 2) ", 间距Y=" (rtos gapY 2 2) ", 每行=" (itoa maxCols)))

  (setq shell (vlax-create-object "Shell.Application"))
  (setq folder (vlax-invoke shell 'BrowseForFolder 0 "请选择图片文件夹" 0 0))
  (if (null folder)
    (progn
      (*error* "CANCEL")
      (princ "\n已取消。")
    )
    (progn
      (setq folderSelf (vlax-get-property folder 'Self))
      (setq path (vlax-get-property folderSelf 'Path))
      (if (not (eq (substr path (strlen path)) "\\")) (setq path (strcat path "\\")))
      (setq files (XYD_BATCHOLE:collect-files path))

      (if (null files)
        (alert "文件夹中未找到图片。")
        (progn
          (setq vbsFile (strcat (getvar "TEMPPREFIX") "XYD_BatchOLE_AutoEnter.vbs"))
          (setq fso (vlax-create-object "Scripting.FileSystemObject"))
          (setq fileOut (vlax-invoke fso 'CreateTextFile vbsFile :vlax-true))
          (vlax-invoke fileOut 'WriteLine "WScript.Sleep 300")
          (vlax-invoke fileOut 'WriteLine "Set WshShell = WScript.CreateObject(\"WScript.Shell\")")
          (vlax-invoke fileOut 'WriteLine "WshShell.SendKeys \"{ENTER}\"")
          (vlax-invoke fileOut 'Close)
          (XYD_BATCHOLE:release-object fileOut)
          (XYD_BATCHOLE:release-object fso)

          (setq wscript (vlax-create-object "WScript.Shell"))
          (princ "\n正在启动 Word 引擎...")
          (setq wordApp (vlax-get-or-create-object "Word.Application"))
          (if (null wordApp)
            (alert "需要安装 Microsoft Word 才能使用当前 LSP 批量嵌图方案。")
            (progn
              (vlax-put-property wordApp 'Visible :vlax-false)
              (setq docs (vlax-get-property wordApp 'Documents))
              (setq doc (vlax-invoke docs 'Add))
              (setq inlineShapes (vlax-get-property doc 'InlineShapes))
              (setq wordOptions (vlax-get-property wordApp 'Options))
              (vl-catch-all-apply 'vlax-put-property (list wordOptions 'CheckSpellingAsYouType :vlax-false))
              (vl-catch-all-apply 'vlax-put-property (list wordOptions 'CheckGrammarAsYouType :vlax-false))

              (setq currentX (car startPt))
              (setq currentY (cadr startPt))
              (setq colCount 0)
              (setq rowMaxHeight targetHeight)

              (princ (strcat "\n共找到 " (itoa (length files)) " 张图片。处理中..."))
              (foreach file files
                (if (>= colCount maxCols)
                  (progn
                    (setq currentX startX)
                    (setq currentY (- currentY (+ rowMaxHeight gapY)))
                    (setq colCount 0)
                    (setq rowMaxHeight targetHeight)
                  )
                )

                (setq fullpath (strcat path file))
                (princ (strcat "\n正在导入: " file "... "))
                (setq currentW (XYD_BATCHOLE:paste-one doc inlineShapes wscript vbsFile fullpath currentX currentY targetHeight))
                (if currentW
                  (progn
                    (setq currentX (+ currentX currentW gapX))
                    (setq colCount (1+ colCount))
                    (princ "完成。")
                  )
                  (princ "失败。")
                )
              )
              (princ "\n\n全部完成。")
            )
          )
        )
      )
      (*error* "CANCEL")
    )
  )
  (princ)
)

(princ "\nXYD_BATCHOLE.lsp 已加载。")
(princ)
